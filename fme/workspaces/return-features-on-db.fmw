FME workspace return-features-on-db.fmw
Title: Real Time Drawing: Return all features on database
Description: This workspace is subscribed to an FME Server Topic. When the topic receives a message, this workspace reads the featuers of the real time drawing table and sends them to all listeners through web sockets.
History: 2014-06-17,Arash Ouji,Initial Creation

Parameters:
- SourceDataset_POSTGIS_2 = demo   # Database

Readers:
- POSTGIS_2: POSTGIS from $(SourceDataset_POSTGIS_2)

Note: This workspace is subscribed to an FME Server Topic. When the topic receives a message, this workspace read the contents of the databse and sends them to all listeners through web sockets
real_time_drawing (reader POSTGIS_2)
    attributes: id serial
    -> GeometryExtractor_2
Note: Aggregate all features
Aggregator_2
    SEP = ,
    ACCUM_ATTRS_NAME = No
    ORDERED = No
    MODE = Geometry - Assemble One Level
    AGGREGATE_TYPE = Homogeneous Collection (If Possible)
    CONCAT_ATTRS = _result
    AGGREGATE -> StringConcatenator_2
Note: Create Final Json message text
StringConcatenator_2
    VAL_ATTR = _concatenated
    PARM_LINE:
      {"type": "FeatureCollection",
        "features": [
              @Value(_result)
              ]
          }
    -> WebSocketSender
Note: Send the Json message containing / all existing items through web sockets
WebSocketSender
    PREAMBLE:
      {

      ws_op : 'open',

      ws_stream_id : 'real_time_drawing_on_page_load_out',

      }
    DATA:
      {

      ws_op : 'send',

      ws_msg : @Value(_concatenated)

      }
    HOST = wss://localhost:7078

Bookmark: Create Json Objects containing geometries and ids
GeometryExtractor_2
    ATTR = _geometry
    KIND_LONG = GeoJSON
    -> JSONTemplater_2
JSONTemplater_2
    VISIBLE_QUERY_VALIDATE = Yes
    RESULT_ATTRIBUTE = _result
    ROOT_QUERY_EXPR:
      {
          "type": "Feature",
          "geometry": fme:get-json-attribute("_geometry"),
          "id" : fme:get-attribute("id")
      }
    -> Aggregator_2

FME workspace real-time-drawing-edits-tracker.fmw
Title: Real Time Drawing: Real Time Edit  handler
Description: This workspace uses web sockets to receive user edits, saves the edits to a database and notifies all users about the changes through a web socket.
History: 2014-06-17,Arash Ouji,Initial Creation

Parameters:
- operation = INSERT   # Operation
- objectid = 33   # Object ID
- geometry = fse   # Geometry

Bookmark: Run once with this Creator enabled in order to create PostGIS Table, then disable
Creator_2 [off]
    GEOMTYPE = Geometry Object
    NUM = 1
    CREATED -> SQLExecutor_3
SQLExecutor_3
    COMBINE_GEOM = Initiator Geometry Only
    POSTGIS_PORT = 5432
    POSTGIS_USER_NAME = demo
    COMBINE_ATTRS = Keep Result Attributes if Conflict
    FORMAT = POSTGIS
    POSTGIS_HOST = your-postgis-server
    POSTGIS_PASSWORD =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
    DATASET = FME_EXPOSE:HOST|your-postgis-server|PORT|5432|DATASET|demo|USER_NAME|demo|PASSWORD|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
    SQL_STATEMENT:
      FME_SQL_DELIMITER ;
      create table real_time_drawing(id serial NOT NULL);
      SELECT AddGeometryColumn('real_time_drawing', 'geom', 4467, 'Geometry', 2);
    EXPOSED_ATTRIBUTE_LIST = id

Bookmark: Handle user edits
Creator_3
    GEOMTYPE = Geometry Object
    NUM = 1
    CREATED -> WebSocketReceiver
Note: Waits for user edits
WebSocketReceiver
    ATTRNAME = message
    HOST = wss://localhost:7078
    PREAMBLE:
      {

      ws_op : 'open',

      ws_stream_id : 'real_time_drawing_update_in',

      }
    -> JSONExtractor
Note: Parse received message
JSONExtractor
    JSON_ATTR = message
    EXTRACT_QUERY_TABLE = geometry json["geometry"] id json["id"] db-operation json["operation"]
    EVALUATED -> GeometryReplacer
Note: Turn GeoJSON text / into FME Polygon
GeometryReplacer
    SOURCE = @Value(geometry)
    KIND_LONG = GeoJSON
    REMOVE_ATTRIBUTE = No
    -> GeometryValidator
Note: Check if input / polygon is valid
GeometryValidator
    ARC_ENDPOINT_TOLERANCE_MODE = Auto
    DUP_COORDS_CHECK_Z = Yes
    PRESETS = Custom
    REPAIR = No
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PLANAR_TOLERANCE_MODE = Auto
    ISSUE_ATTR_NAME = _issues
    TYPE_REPAIR = TYPE_REPAIR
    CHECK_HOLE_TOUCHING_POLYGON = No
    PASSED -> GeometryExtractor
Note: Replace GeoJson with WKT / For use in SQL query
GeometryExtractor
    KIND_LONG = OGC Well Known Text
    ATTR = _geometry
    OGCVERSION = 1.1
    -> AttributeCreator
Note: Create SQL Insert, Update or delete, / depending on type of user edit received / All statements are set to return the changed / row's id
AttributeCreator
    ATTR_LIST = sql,"FME_CONDITIONAL:DEFAULT_VALUE'_FME_NO_OP_'BOOL_OP;OR;COMPOSITE_TEST;<Unused>;TEST @Value(db-operation) = I'insert into real_time_drawing (geom) values (ST_GeomFromText('@Value(_geometry)', 4467)) RETURNING id'BOOL_OP;OR;COMPOSITE_TEST;<Unused>;TEST @Value(db-operation) = U'update real_time_drawing set geom=ST_GeomFromText('@Value(_geometry)', 4467) where id = @Value(id)  RETURNING id'BOOL_OP;OR;COMPOSITE_TEST;<Unused>;TEST @Value(db-operation) = D'delete from real_time_drawing where id = @Value(id)  RETURNING id'FME_NUM_CONDITIONS4___"
    -> SQLExecutor
Note: Run query on database
SQLExecutor
    COMBINE_GEOM = Initiator Geometry Only
    POSTGIS_PORT = 5432
    POSTGIS_USER_NAME = demo
    COMBINE_ATTRS = Keep Result Attributes if Conflict
    FORMAT = POSTGIS
    POSTGIS_HOST = my-postgis-server
    POSTGIS_PASSWORD =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
    DATASET = demo
    SQL_STATEMENT = @Value(sql)
    EXPOSED_ATTRIBUTE_LIST = id
    RESULT -> StringReplacer
Note: Update the received message with the / result id when db transaction was an Insert
StringReplacer
    NO_MATCH = _FME_NO_OP_
    REGEXP = no
    REPLACE_TEXT = "id": "@Value(id)"
    SRC_ATTRS = message
    CASE = no
    FIND_TEXT = "id": "null"
    -> WebSocketSender
Note: Send the message back to all / Users
WebSocketSender
    HOST = wss://localhost:7078
    PREAMBLE:
      {

      ws_op : 'open',

      ws_stream_id : 'real_time_drawing_update_out',

      }
    DATA:
      {

      ws_op : 'send',

      ws_msg : @Value(message)

      }
